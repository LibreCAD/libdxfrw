# Optional independent-writer ELLIPSE import observation.
#
# Run with freecadcmd, an ODA-generated AC1015 DWG whose path contains spaces,
# and an isolated --user-cfg. Preference seeding is mandatory and fail-closed:
# LIBDXFRW_FREECAD_USER_CFG must match FreeCAD's active config, beneath
# LIBDXFRW_FREECAD_TEMP_ROOT. Generated DWG/DXF files stay outside the source.
# The OBSERVATION marker proves route/field capture only; inspect each
# semantic_match value before making any FreeCAD support claim.

import hashlib
import json
import math
import os
import platform
import subprocess
import sys
import tempfile

import FreeCAD as App


sample = os.environ.get("LIBDXFRW_FREECAD_DWG")
if not sample or not os.path.isfile(sample):
    raise RuntimeError("LIBDXFRW_FREECAD_DWG must name an existing DWG sample")
if " " not in os.path.abspath(sample):
    raise RuntimeError("ELLIPSE runtime qualification requires an input path with spaces")
if App.GuiUp:
    raise RuntimeError("This qualification uses freecadcmd and requires the C++ Import backend")

draft_path = os.path.join(App.getResourceDir(), "Mod", "Draft")
sys.path.insert(0, draft_path)

import importDWG
import importDXF
import Import


preferences = App.ParamGet("User parameter:BaseApp/Preferences/Mod/Draft")
if preferences.GetBool("dxfUseLegacyImporter", False):
    raise RuntimeError("This check requires FreeCAD's default C++ DXF importer")


def same_path(left, right):
    return os.path.normcase(os.path.abspath(left)) == os.path.normcase(
        os.path.abspath(right)
    )


def digest(path):
    sha = hashlib.sha256()
    with open(path, "rb") as stream:
        for chunk in iter(lambda: stream.read(1024 * 1024), b""):
            sha.update(chunk)
    return sha.hexdigest()


def vector_tuple(value):
    return (float(value.x), float(value.y), float(value.z))


def optional_vector(obj, name):
    try:
        return vector_tuple(getattr(obj, name))
    except (AttributeError, RuntimeError, TypeError):
        return None


def optional_float(obj, name):
    try:
        return float(getattr(obj, name))
    except (AttributeError, RuntimeError, TypeError, ValueError):
        return None


def close(actual, expected, tolerance=1e-7):
    return actual is not None and abs(actual - expected) <= tolerance


def tuple_close(actual, expected, tolerance=1e-7):
    return actual is not None and len(actual) == len(expected) and all(
        close(a, e, tolerance) for a, e in zip(actual, expected)
    )


def distance(left, right):
    if left is None:
        return float("inf")
    return math.sqrt(sum((a - b) ** 2 for a, b in zip(left, right)))


def ellipse_point(spec, parameter):
    center = spec["center"]
    major = spec["major_axis"]
    normal = spec["normal"]
    minor = (
        normal[1] * major[2] - normal[2] * major[1],
        normal[2] * major[0] - normal[0] * major[2],
        normal[0] * major[1] - normal[1] * major[0],
    )
    return tuple(
        center[index]
        + major[index] * math.cos(parameter)
        + spec["ratio"] * minor[index] * math.sin(parameter)
        for index in range(3)
    )


def endpoint_set_matches(actual, expected):
    if len(actual) != 2:
        return False
    return (
        tuple_close(actual[0], expected[0]) and tuple_close(actual[1], expected[1])
    ) or (
        tuple_close(actual[0], expected[1]) and tuple_close(actual[1], expected[0])
    )


config_root = os.environ.get("LIBDXFRW_FREECAD_TEMP_ROOT")
expected_user_cfg = os.environ.get("LIBDXFRW_FREECAD_USER_CFG")
active_user_cfg = App.ConfigGet("UserParameter")
if (
    os.environ.get("LIBDXFRW_FREECAD_SEED_ISOLATED_PREFERENCES") != "1"
    or not config_root
    or not expected_user_cfg
    or not active_user_cfg
):
    raise RuntimeError("an explicitly isolated FreeCAD --user-cfg is required")
real_root = os.path.realpath(config_root)
real_temp = os.path.realpath(tempfile.gettempdir())
real_user_cfg = os.path.realpath(active_user_cfg)
if (
    not os.path.isdir(real_root)
    or real_root == real_temp
    or os.path.commonpath((real_temp, real_root)) != real_temp
    or not same_path(active_user_cfg, expected_user_cfg)
    or os.path.commonpath((real_root, real_user_cfg)) != real_root
):
    raise RuntimeError("FreeCAD did not load the requested isolated temp config")

discovery = os.environ.get("LIBDXFRW_FREECAD_DISCOVERY", "path").lower()
if discovery != "path":
    raise RuntimeError("this ELLIPSE check requires the explicit PATH discovery lane")
importDWG.params.set_param("DWGConversion", 1)
importDWG.params.set_param("TeighaFileConverter", "")
if importDWG.params.get_param("DWGConversion") != 1:
    raise RuntimeError("isolated FreeCAD preferences did not enable DWGConversion=1")

expected_binary = os.environ.get("LIBDXFRW_FREECAD_EXPECT_DWG2DXF")
expected_hash = os.environ.get("LIBDXFRW_FREECAD_EXPECT_DWG2DXF_SHA256")
if not expected_binary or not expected_hash:
    raise RuntimeError("expected installed dwg2dxf path and SHA-256 are required")

draft_path = os.path.join(App.getResourceDir(), "Mod", "Draft")
sys.path.insert(0, draft_path)
importDWG_module = importDWG
importDXF_module = importDXF

captured = {}
original_convert = importDWG_module.convertToDxf
original_open = importDXF_module.open
original_reporter = importDXF_module.DxfImportReporter
original_popen = subprocess.Popen
original_oda = importDWG_module.get_oda_converter
original_qcad = importDWG_module.get_qcad_converter
original_read_dxf = Import.readDXF


def capture_read_dxf(filename, *args, **kwargs):
    captured["cpp_import_dxf"] = filename
    return original_read_dxf(filename, *args, **kwargs)


def capture_open(filename, *args, **kwargs):
    captured["open_handoff"] = filename
    return original_open(filename, *args, **kwargs)


def capture_convert(filename):
    processes = []

    def capture_popen(*args, **kwargs):
        process = original_popen(*args, **kwargs)
        processes.append(process)
        return process

    subprocess.Popen = capture_popen
    importDWG_module.get_oda_converter = lambda: None
    importDWG_module.get_qcad_converter = lambda: None
    try:
        result = original_convert(filename)
    finally:
        subprocess.Popen = original_popen
        importDWG_module.get_oda_converter = original_oda
        importDWG_module.get_qcad_converter = original_qcad
    captured["converted_dxf"] = result
    captured["converter_processes"] = processes
    return result


class CapturingReporter(original_reporter):
    def __init__(self, filename, stats_dict, total_time=0.0):
        captured["stats"] = stats_dict
        super().__init__(filename, stats_dict, total_time)


def edge_signature(obj, edge):
    curve = edge.Curve
    vertices = [vector_tuple(vertex.Point) for vertex in edge.Vertexes]
    box = obj.Shape.BoundBox
    box_center = (
        (box.XMin + box.XMax) / 2.0,
        (box.YMin + box.YMax) / 2.0,
        (box.ZMin + box.ZMax) / 2.0,
    )
    return {
        "object_name": obj.Name,
        "object_type": obj.TypeId,
        "curve_type": type(curve).__name__,
        "center": optional_vector(curve, "Center"),
        "bbox_center": box_center,
        "major_radius": optional_float(curve, "MajorRadius"),
        "minor_radius": optional_float(curve, "MinorRadius"),
        "axis": optional_vector(curve, "Axis"),
        "x_axis": optional_vector(curve, "XAxis"),
        "first_parameter": optional_float(edge, "FirstParameter"),
        "last_parameter": optional_float(edge, "LastParameter"),
        "closed": bool(edge.isClosed()),
        "valid": bool(obj.Shape.isValid()),
        "edge_count": len(obj.Shape.Edges),
        "face_count": len(obj.Shape.Faces),
        "endpoints": vertices,
        "length": float(edge.Length),
    }


specs = [
    {
        "name": "full_xy",
        "center": (10.0, 20.0, 0.0),
        "major_axis": (5.0, 0.0, 0.0),
        "major_direction": (1.0, 0.0, 0.0),
        "major_radius": 5.0,
        "minor_radius": 2.5,
        "ratio": 0.5,
        "normal": (0.0, 0.0, 1.0),
        "start": 0.0,
        "end": math.tau,
        "closed": True,
    },
    {
        "name": "elevated_partial",
        "center": (1.0, 2.0, 30.0),
        "major_axis": (3.0, 0.0, 0.0),
        "major_direction": (1.0, 0.0, 0.0),
        "major_radius": 3.0,
        "minor_radius": 1.5,
        "ratio": 0.5,
        "normal": (0.0, 0.0, 1.0),
        "start": 0.25,
        "end": 1.25,
        "closed": False,
    },
    {
        "name": "tilted_partial",
        "center": (-10.0, 5.0, 2.0),
        "major_axis": (2.0, 0.0, -1.5),
        "major_direction": (0.8, 0.0, -0.6),
        "major_radius": 2.5,
        "minor_radius": 1.25,
        "ratio": 0.5,
        "normal": (0.6, 0.0, 0.8),
        "start": 0.25,
        "end": 1.75,
        "closed": False,
    },
]

importDWG_module.convertToDxf = capture_convert
importDXF_module.open = capture_open
importDXF_module.DxfImportReporter = CapturingReporter
Import.readDXF = capture_read_dxf

doc = None
try:
    doc = importDWG_module.open(sample)
    if doc is None:
        raise AssertionError("Draft.importDWG.open returned no document")

    dxf_path = captured.get("converted_dxf")
    if not dxf_path or not os.path.isfile(dxf_path):
        raise AssertionError("Draft DWG conversion produced no DXF output")
    processes = captured.get("converter_processes", [])
    if len(processes) != 1:
        raise AssertionError("expected exactly one converter process; got %d" % len(processes))
    process = processes[0]
    converter = importDWG_module.get_libredwg_converter("dwg2dxf")
    args = process.args
    if not converter or not isinstance(args, (list, tuple)) or len(args) != 4:
        raise AssertionError("FreeCAD did not invoke the expected dwg2dxf command")
    path_candidates = [
        os.path.join(directory, executable)
        for directory in os.environ.get("PATH", "").split(os.pathsep)
        if directory
        for executable in ("dwg2dxf", "dwg2dxf.exe")
    ]
    if not any(same_path(candidate, converter) for candidate in path_candidates):
        raise AssertionError("FreeCAD did not resolve dwg2dxf through PATH")
    if not same_path(converter, expected_binary) or digest(converter).lower() != expected_hash.lower():
        raise AssertionError("FreeCAD resolved the wrong installed binary/hash")
    if not same_path(args[0], converter) or not same_path(args[1], sample):
        raise AssertionError("FreeCAD invoked an unexpected converter/input: %r" % (args,))
    if args[2] != "-o" or not same_path(args[3], dxf_path) or process.returncode != 0:
        raise AssertionError("FreeCAD converter argv/status mismatch: %r" % (args,))
    if not same_path(captured.get("open_handoff", ""), dxf_path):
        raise AssertionError("Draft.importDWG.open imported a different DXF")
    if not same_path(captured.get("cpp_import_dxf", ""), dxf_path):
        raise AssertionError("C++ Import.readDXF received a different DXF")

    stats = captured.get("stats") or {}
    entity_counts = stats.get("entityCounts", {})
    if entity_counts.get("ELLIPSE", 0) != 3:
        raise AssertionError("C++ DXF importer did not count three ELLIPSEs: %r" % entity_counts)
    unsupported = stats.get("unsupportedFeatures", {})

    objects = []
    signatures = []
    for obj in doc.Objects:
        shape = getattr(obj, "Shape", None)
        has_shape = shape is not None and not shape.isNull()
        objects.append({"name": obj.Name, "type": obj.TypeId, "has_shape": has_shape})
        if has_shape:
            for edge in shape.Edges:
                signatures.append(edge_signature(obj, edge))

    matched = set()
    observations = []
    for spec in specs:
        candidates = [
            (distance(signature["center"] or signature["bbox_center"], spec["center"]), index, signature)
            for index, signature in enumerate(signatures)
            if index not in matched
        ]
        candidates.sort(key=lambda item: item[0])
        signature = candidates[0][2] if candidates and candidates[0][0] <= 1e-4 else None
        if signature is not None:
            matched.add(candidates[0][1])
        observation = {"name": spec["name"], "expected": spec, "observed": signature}
        if signature is None:
            observation["semantic_match"] = False
            observation["differences"] = ["no shape was associated with expected center"]
        else:
            expected_start = ellipse_point(spec, spec["start"])
            expected_end = ellipse_point(spec, spec["end"])
            checks = {
                "center": tuple_close(signature["center"], spec["center"]),
                "major_radius": close(signature["major_radius"], spec["major_radius"]),
                "minor_radius": close(signature["minor_radius"], spec["minor_radius"]),
                "major_direction": tuple_close(
                    signature["x_axis"], spec["major_direction"]
                ),
                "axis": tuple_close(signature["axis"], spec["normal"]),
                "closure": signature["closed"] == spec["closed"],
            }
            if spec["closed"]:
                checks["full_parameters"] = (
                    close(signature["first_parameter"], 0.0)
                    and close(signature["last_parameter"], math.tau)
                )
            else:
                checks["arc_parameters"] = (
                    close(signature["first_parameter"], spec["start"])
                    and close(signature["last_parameter"], spec["end"])
                )
                checks["arc_endpoints"] = endpoint_set_matches(
                    signature["endpoints"], (expected_start, expected_end)
                )
            observation["checks"] = checks
            observation["semantic_match"] = all(checks.values()) and signature["valid"]
            observation["differences"] = [key for key, result in checks.items() if not result]
        observations.append(observation)

    result = {
        "freecad_version": list(App.Version()),
        "platform": platform.platform(),
        "architecture": platform.machine(),
        "importer_backend": "Import",
        "import_mode": preferences.GetInt("DxfImportMode", 2),
        "dwg_conversion": importDWG_module.params.get_param("DWGConversion"),
        "discovery": discovery,
        "converter": os.path.abspath(converter),
        "converter_sha256": digest(converter),
        "converter_argv": list(args),
        "converter_returncode": process.returncode,
        "source": os.path.abspath(sample),
        "source_sha256": digest(sample),
        "converted_dxf": os.path.abspath(dxf_path),
        "converted_dxf_sha256": digest(dxf_path),
        "import_handoffs": {
            "draft_open": captured.get("open_handoff"),
            "cpp_import": captured.get("cpp_import_dxf"),
        },
        "ellipse_entity_count": entity_counts.get("ELLIPSE"),
        "unsupported_features": {
            key: len(values) for key, values in sorted(unsupported.items())
        },
        "objects": objects,
        "edge_signatures": signatures,
        "ellipse_results": observations,
        "all_ellipse_semantics_match": all(
            item["semantic_match"] for item in observations
        ),
        "support_claim": "narrow semantic match only when each semantic_match is true",
    }
    print("FREECAD_DWG2DXF_3D_ELLIPSE_OBSERVATION=" + json.dumps(result, sort_keys=True))
finally:
    importDWG_module.convertToDxf = original_convert
    importDXF_module.open = original_open
    importDXF_module.DxfImportReporter = original_reporter
    Import.readDXF = original_read_dxf
    if doc is not None and doc.Name in App.listDocuments():
        App.closeDocument(doc.Name)
    dxf_path = captured.get("converted_dxf")
    if dxf_path:
        temp_root = os.path.realpath(tempfile.gettempdir())
        output_dir = os.path.realpath(os.path.dirname(dxf_path))
        if output_dir != temp_root and os.path.dirname(output_dir) == temp_root:
            try:
                if os.path.lexists(dxf_path):
                    os.remove(dxf_path)
                os.rmdir(output_dir)
            except OSError as error:
                print("FREECAD_DWG2DXF_3D_ELLIPSE_CLEANUP_WARNING=" + str(error))
