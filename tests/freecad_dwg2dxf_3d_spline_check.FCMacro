# Optional end-to-end ODA-authored DWG -> dwg2dxf -> FreeCAD SPLINE check.
# The DWG is generated by dwg2dxf_freecad_3d_spline_cli in the build tree.

import hashlib
import json
import os
import platform
import subprocess
import sys

import FreeCAD as App


sample = os.environ.get("LIBDXFRW_FREECAD_DWG")
if not sample or not os.path.isfile(sample):
    raise RuntimeError("LIBDXFRW_FREECAD_DWG must name an existing generated DWG")

sys.path.insert(0, os.path.join(App.getResourceDir(), "Mod", "Draft"))
import importDWG
import importDXF

preferences = App.ParamGet("User parameter:BaseApp/Preferences/Mod/Draft")
if preferences.GetBool("dxfUseLegacyImporter", False):
    raise RuntimeError("This check requires FreeCAD's default C++ DXF importer")

captured = {}
original_convert = importDWG.convertToDxf
original_dxf_open = importDXF.open
original_reporter = importDXF.DxfImportReporter
original_popen = subprocess.Popen
original_oda_converter = importDWG.get_oda_converter
original_qcad_converter = importDWG.get_qcad_converter


def capture_convert(filename):
    processes = []

    def capture_popen(*args, **kwargs):
        process = original_popen(*args, **kwargs)
        processes.append(process)
        return process

    subprocess.Popen = capture_popen
    importDWG.get_oda_converter = lambda: None
    importDWG.get_qcad_converter = lambda: None
    try:
        result = original_convert(filename)
    finally:
        subprocess.Popen = original_popen
        importDWG.get_oda_converter = original_oda_converter
        importDWG.get_qcad_converter = original_qcad_converter
    captured["dxf"] = result
    captured["converter_processes"] = processes
    return result


def capture_dxf_open(filename, *args, **kwargs):
    captured["imported_dxf"] = filename
    return original_dxf_open(filename, *args, **kwargs)


def same_path(left, right):
    return os.path.normcase(os.path.abspath(left)) == os.path.normcase(os.path.abspath(right))


class CapturingReporter(original_reporter):
    def __init__(self, filename, stats_dict, total_time=0.0):
        captured["stats"] = stats_dict
        super().__init__(filename, stats_dict, total_time)


def digest(path):
    sha = hashlib.sha256()
    with open(path, "rb") as stream:
        for chunk in iter(lambda: stream.read(1024 * 1024), b""):
            sha.update(chunk)
    return sha.hexdigest()


def close(actual, expected):
    return abs(actual - expected) < 1e-7


def point_tuple(point):
    return (float(point.x), float(point.y), float(point.z))


def edge_endpoints(edge):
    return sorted(point_tuple(vertex.Point) for vertex in edge.Vertexes)


def endpoints_match(actual, expected):
    return len(actual) == 2 and all(
        all(close(a, e) for a, e in zip(actual_point, expected_point))
        for actual_point, expected_point in zip(actual, sorted(expected))
    )


def midpoint(edge):
    parameter = (edge.FirstParameter + edge.LastParameter) * 0.5
    return point_tuple(edge.valueAt(parameter))


importDWG.convertToDxf = capture_convert
importDXF.open = capture_dxf_open
importDXF.DxfImportReporter = CapturingReporter

doc = None
try:
    doc = importDWG.open(sample)
    if doc is None:
        raise AssertionError("Draft.importDWG.open returned no document")

    dxf_path = captured.get("dxf")
    if not dxf_path or not os.path.isfile(dxf_path):
        raise AssertionError("Draft DWG conversion did not produce an auditable DXF")
    processes = captured.get("converter_processes", [])
    if len(processes) != 1:
        raise AssertionError(
            "expected exactly one converter subprocess with fallbacks disabled; got %d"
            % len(processes)
        )
    process = processes[0]
    args = process.args
    converter = importDWG.get_libredwg_converter("dwg2dxf")
    if not converter or not isinstance(args, (list, tuple)) or len(args) != 4:
        raise AssertionError("FreeCAD did not invoke the expected dwg2dxf command")
    if not same_path(args[0], converter) or not same_path(args[1], sample):
        raise AssertionError("FreeCAD invoked dwg2dxf with unexpected argv: %r" % (args,))
    if args[2] != "-o" or not same_path(args[3], dxf_path):
        raise AssertionError("FreeCAD did not use the expected dwg2dxf output: %r" % (args,))
    if process.returncode != 0:
        raise AssertionError("dwg2dxf exited with status %r" % process.returncode)
    imported_path = captured.get("imported_dxf")
    if not imported_path or not same_path(imported_path, dxf_path):
        raise AssertionError("FreeCAD imported a different DXF than dwg2dxf produced")

    features = [obj for obj in doc.Objects if obj.TypeId == "Part::Feature"]
    if len(features) != 4:
        raise AssertionError("expected four Part::Feature SPLINEs; got %d" % len(features))
    for feature in features:
        shape = feature.Shape
        if shape.isNull() or not shape.isValid() or len(shape.Edges) != 1 or shape.Faces:
            raise AssertionError("FreeCAD produced an invalid SPLINE shape: %s" % feature.Name)

    expectations = [
        {
            "name": "nonplanar_control",
            "endpoints": [(1.0, 2.0, 3.0), (10.0, 8.0, 22.0)],
            "midpoint": (5.5, 4.25, 12.125),
        },
        {
            "name": "planar_oblique_control",
            "endpoints": [(1.0, 0.0, 1.0), (3.0, 0.0, 3.0)],
            "midpoint": (1.25, 0.75, 2.75),
        },
        {
            "name": "nonplanar_fit",
            "endpoints": [(0.0, 1.0, 2.0), (3.0, 6.0, 10.0)],
            "midpoint": None,
        },
        {
            "name": "near_planar_control_within_tolerance",
            "endpoints": [(0.0, 0.0, 0.0), (0.0, 1.0, 2.00000001)],
            "midpoint": None,
        },
    ]
    unmatched = list(features)
    observed = []
    for expected in expectations:
        selected = None
        for feature in unmatched:
            endpoints = edge_endpoints(feature.Shape.Edges[0])
            if endpoints_match(endpoints, expected["endpoints"]):
                selected = (feature, endpoints)
                break
        if selected is None:
            raise AssertionError(
                "FreeCAD SPLINE endpoints mismatch for %s" % expected["name"]
            )
        feature, endpoints = selected
        unmatched.remove(feature)
        actual_midpoint = midpoint(feature.Shape.Edges[0])
        if expected["midpoint"] is not None and any(
            not close(actual, wanted)
            for actual, wanted in zip(actual_midpoint, expected["midpoint"])
        ):
            raise AssertionError(
                "%s curve midpoint mismatch: expected %r, got %r"
                % (expected["name"], expected["midpoint"], actual_midpoint)
            )
        observed.append(
            {
                "case": expected["name"],
                "feature": feature.Name,
                "edge_endpoints": endpoints,
                "edge_midpoint": actual_midpoint,
            }
        )

    stats = captured.get("stats") or {}
    entity_counts = stats.get("entityCounts", {})
    if entity_counts.get("SPLINE", 0) != 4:
        raise AssertionError("FreeCAD did not report four SPLINEs: %r" % entity_counts)
    unsupported = stats.get("unsupportedFeatures", {})
    if unsupported.get("SPLINE"):
        raise AssertionError("FreeCAD reported SPLINE unsupported: %r" % unsupported)

    result = {
        "status": "pass",
        "freecad_version": list(App.Version()),
        "platform": platform.platform(),
        "architecture": platform.machine(),
        "importer": "C++",
        "import_mode": preferences.GetInt("DxfImportMode", 2),
        "converter": converter,
        "converter_argv": args,
        "converter_returncode": process.returncode,
        "source": os.path.basename(sample),
        "source_sha256": digest(sample),
        "imported_dxf_path": imported_path,
        "dxf_sha256": digest(imported_path),
        "entity_counts": entity_counts,
        "unsupported_features": {
            key: len(values) for key, values in sorted(unsupported.items())
        },
        "splines": observed,
    }
    print("FREECAD_DWG2DXF_3D_SPLINE_ASSERTIONS_PASS=" + json.dumps(result, sort_keys=True))
finally:
    importDWG.convertToDxf = original_convert
    importDXF.open = original_dxf_open
    importDXF.DxfImportReporter = original_reporter
    if doc is not None and doc.Name in App.listDocuments():
        App.closeDocument(doc.Name)
