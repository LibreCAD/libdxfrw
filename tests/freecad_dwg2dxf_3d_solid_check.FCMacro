# Pinned FreeCAD C++ importer probe for one locally-authored elevated SOLID.
# Generated DWG/DXF and the isolated FreeCAD profile must stay outside source.

import hashlib
import json
import os
import platform
import subprocess
import sys
import tempfile

import FreeCAD as App


sample = os.environ.get("LIBDXFRW_FREECAD_DWG")
if not sample or not os.path.isfile(sample):
    raise RuntimeError("LIBDXFRW_FREECAD_DWG must name an existing DWG sample")
if " " not in os.path.abspath(sample):
    raise RuntimeError("SOLID qualification requires an input path with spaces")
if App.GuiUp:
    raise RuntimeError("This check requires FreeCADCmd and the C++ Import backend")

legacy = App.ParamGet(
    "User parameter:BaseApp/Preferences/Mod/Draft"
).GetBool("dxfUseLegacyImporter", False)
if legacy:
    raise RuntimeError("This check requires FreeCAD's default C++ DXF importer")

temp_root = os.environ.get("LIBDXFRW_FREECAD_TEMP_ROOT")
expected_user_cfg = os.environ.get("LIBDXFRW_FREECAD_USER_CFG")
active_user_cfg = App.ConfigGet("UserParameter")
if (
    os.environ.get("LIBDXFRW_FREECAD_SEED_ISOLATED_PREFERENCES") != "1"
    or not temp_root
    or not expected_user_cfg
    or not active_user_cfg
):
    raise RuntimeError("an isolated FreeCAD --user-cfg and temp root are required")
real_root = os.path.realpath(temp_root)
real_temp = os.path.realpath(tempfile.gettempdir())
real_user_cfg = os.path.realpath(active_user_cfg)
if (
    not os.path.isdir(real_root)
    or real_root == real_temp
    or os.path.commonpath((real_temp, real_root)) != real_temp
    or os.path.normcase(real_user_cfg) != os.path.normcase(
        os.path.realpath(expected_user_cfg)
    )
    or os.path.commonpath((real_root, real_user_cfg)) != real_root
):
    raise RuntimeError("FreeCAD did not load the requested isolated user config")

import os.path

draft_path = os.path.join(App.getResourceDir(), "Mod", "Draft")
sys.path.insert(0, draft_path)
import importDWG
import importDXF

if os.environ.get("LIBDXFRW_FREECAD_DISCOVERY") != "path":
    raise RuntimeError("this SOLID probe requires the attributed PATH discovery lane")
importDWG.params.set_param("DWGConversion", 1)
importDWG.params.set_param("TeighaFileConverter", "")
if (
    importDWG.params.get_param("DWGConversion") != 1
    or importDWG.params.get_param("TeighaFileConverter")
):
    raise RuntimeError("isolated FreeCAD preferences did not select PATH discovery")

expected_binary = os.environ.get("LIBDXFRW_FREECAD_EXPECT_DWG2DXF")
expected_hash = os.environ.get("LIBDXFRW_FREECAD_EXPECT_DWG2DXF_SHA256")
if not expected_binary or not expected_hash:
    raise RuntimeError("expected installed dwg2dxf path and SHA-256 are required")


def same_path(left, right):
    return os.path.normcase(os.path.realpath(left)) == os.path.normcase(
        os.path.realpath(right)
    )


def digest(path):
    sha = hashlib.sha256()
    with open(path, "rb") as stream:
        for chunk in iter(lambda: stream.read(1024 * 1024), b""):
            sha.update(chunk)
    return sha.hexdigest()


captured = {}
original_convert = importDWG.convertToDxf
original_open = importDXF.open
original_reporter = importDXF.DxfImportReporter
original_popen = subprocess.Popen
original_oda = importDWG.get_oda_converter
original_qcad = importDWG.get_qcad_converter


def capture_convert(filename):
    processes = []

    def capture_popen(*args, **kwargs):
        process = original_popen(*args, **kwargs)
        processes.append(process)
        return process

    subprocess.Popen = capture_popen
    importDWG.get_oda_converter = lambda: None
    importDWG.get_qcad_converter = lambda: None
    try:
        result = original_convert(filename)
    finally:
        subprocess.Popen = original_popen
        importDWG.get_oda_converter = original_oda
        importDWG.get_qcad_converter = original_qcad
    captured["converted_dxf"] = result
    captured["converter_processes"] = processes
    return result


def capture_open(filename, *args, **kwargs):
    captured["imported_dxf"] = filename
    return original_open(filename, *args, **kwargs)


class CapturingReporter(original_reporter):
    def __init__(self, filename, stats_dict, total_time=0.0):
        captured["stats"] = stats_dict
        super().__init__(filename, stats_dict, total_time)


importDWG.convertToDxf = capture_convert
importDXF.open = capture_open
importDXF.DxfImportReporter = CapturingReporter
doc = None
try:
    doc = importDWG.open(sample)
    if doc is None:
        raise AssertionError("Draft.importDWG.open() returned no document")

    processes = captured.get("converter_processes", [])
    if len(processes) != 1:
        raise AssertionError("expected exactly one converter process")
    process = processes[0]
    if not isinstance(process.args, (list, tuple)) or len(process.args) != 4:
        raise AssertionError("FreeCAD did not use the exact input -o output argv")
    if not same_path(process.args[0], expected_binary):
        raise AssertionError("FreeCAD invoked an unexpected dwg2dxf executable")
    if not same_path(importDWG.get_libredwg_converter("dwg2dxf"), expected_binary):
        raise AssertionError("PATH discovery did not resolve the installed executable")
    if not same_path(process.args[1], sample) or process.args[2] != "-o":
        raise AssertionError("FreeCAD converter argv input/option differs from expected")
    if process.returncode != 0:
        raise AssertionError("dwg2dxf returned %r" % process.returncode)
    if digest(expected_binary) != expected_hash:
        raise AssertionError("installed dwg2dxf SHA-256 differs from expectation")

    dxf_path = captured.get("converted_dxf")
    if not dxf_path or not os.path.isfile(dxf_path):
        raise AssertionError("dwg2dxf did not produce its expected DXF")
    if not same_path(process.args[3], dxf_path):
        raise AssertionError("converter output argument differs from its returned path")
    if not same_path(captured.get("imported_dxf", ""), dxf_path):
        raise AssertionError("FreeCAD imported a different DXF than dwg2dxf produced")

    shape_objects = []
    for obj in doc.Objects:
        shape = getattr(obj, "Shape", None)
        if shape is not None and not shape.isNull():
            shape_objects.append(obj)

    stats = captured.get("stats") or {}
    entity_counts = stats.get("entityCounts", {})
    if entity_counts.get("SOLID", 0) != 1:
        raise AssertionError("FreeCAD did not report one SOLID: %r" % entity_counts)
    unsupported = stats.get("unsupportedFeatures", {})
    unsupported_solid_count = sum(
        len(values) for key, values in unsupported.items() if "SOLID" in key
    )
    if len(shape_objects) != 0 or unsupported_solid_count != 1:
        raise AssertionError(
            "pinned FreeCAD 1.1.3 SOLID limitation changed: %d shapes, unsupported=%r"
            % (len(shape_objects), unsupported)
        )

    result = {
        "status": "pass",
        "freecad_version": list(App.Version()),
        "platform": platform.platform(),
        "architecture": platform.machine(),
        "importer": "C++",
        "import_mode": App.ParamGet(
            "User parameter:BaseApp/Preferences/Mod/Draft"
        ).GetInt("DxfImportMode", 2),
        "converter": importDWG.get_libredwg_converter("dwg2dxf"),
        "converter_sha256": digest(expected_binary),
        "converter_argv": process.args,
        "converter_returncode": process.returncode,
        "source_sha256": digest(sample),
        "dxf_path": dxf_path,
        "dxf_sha256": digest(dxf_path),
        "entity_counts": entity_counts,
        "created_shape_count": len(shape_objects),
        "semantic_status": "unsupported_by_pinned_freecad_importer",
        "unsupported_solid_count": unsupported_solid_count,
        "unsupported_features": {
            key: len(values) for key, values in sorted(unsupported.items())
        },
    }
    print(
        "FREECAD_DWG2DXF_SOLID_UNSUPPORTED_AS_EXPECTED="
        + json.dumps(result, sort_keys=True)
    )
finally:
    importDWG.convertToDxf = original_convert
    importDXF.open = original_open
    importDXF.DxfImportReporter = original_reporter
    importDWG.get_oda_converter = original_oda
    importDWG.get_qcad_converter = original_qcad
    subprocess.Popen = original_popen
    if doc is not None and doc.Name in App.listDocuments():
        App.closeDocument(doc.Name)
